(upc:run "C:/temp/cj84a/outputs/cj84A-basic-v010.dwg" "C:/temp/cj84a/operations_v010" "dim-901" (quote (lambda (doc / ms o) (setq ms (vla-get-modelspace doc)) (setq o (vla-adddimrotated ms (upc:pt 0 0) (upc:pt 14630 0) (upc:pt 7315.0 -1500) 0)) (vla-put-stylename o "MCDIM-50") (upc:set o "DIM")
 (setq o (vla-adddimrotated ms (upc:pt 0 0) (upc:pt 3195 0) (upc:pt 1597.5 -900) 0)) (vla-put-stylename o "MCDIM-50") (upc:set o "DIM")
 (setq o (vla-adddimrotated ms (upc:pt 3195 0) (upc:pt 6065 0) (upc:pt 4630.0 -900) 0)) (vla-put-stylename o "MCDIM-50") (upc:set o "DIM")
 (setq o (vla-adddimrotated ms (upc:pt 6065 0) (upc:pt 10785 0) (upc:pt 8425.0 -900) 0)) (vla-put-stylename o "MCDIM-50") (upc:set o "DIM")
 (setq o (vla-adddimrotated ms (upc:pt 10785 0) (upc:pt 12780 0) (upc:pt 11782.5 -900) 0)) (vla-put-stylename o "MCDIM-50") (upc:set o "DIM")
 (setq o (vla-adddimrotated ms (upc:pt 12780 0) (upc:pt 14630 0) (upc:pt 13705.0 -900) 0)) (vla-put-stylename o "MCDIM-50") (upc:set o "DIM")
 (setq o (vla-adddimrotated ms (upc:pt 14630 0) (upc:pt 14630 10335) (upc:pt 16300 5167.5) (/ pi 2))) (vla-put-stylename o "MCDIM-50") (upc:set o "DIM")
 (setq o (vla-adddimrotated ms (upc:pt 14630 0) (upc:pt 14630 1500) (upc:pt 15700 750.0) (/ pi 2))) (vla-put-stylename o "MCDIM-50") (upc:set o "DIM")
 (setq o (vla-adddimrotated ms (upc:pt 14630 1500) (upc:pt 14630 5555) (upc:pt 15700 3527.5) (/ pi 2))) (vla-put-stylename o "MCDIM-50") (upc:set o "DIM")
 (setq o (vla-adddimrotated ms (upc:pt 14630 5555) (upc:pt 14630 8145) (upc:pt 15700 6850.0) (/ pi 2))) (vla-put-stylename o "MCDIM-50") (upc:set o "DIM")
 (setq o (vla-adddimrotated ms (upc:pt 14630 8145) (upc:pt 14630 10335) (upc:pt 15700 9240.0) (/ pi 2))) (vla-put-stylename o "MCDIM-50") (upc:set o "DIM")
 (setq o (vla-adddimrotated ms (upc:pt 10885 3747.0) (upc:pt 14530 3747.0) (upc:pt 12707.5 3747.0) 0)) (vla-put-stylename o "HAUD-100") (upc:set o "DIM")
 (setq o (vla-adddimrotated ms (upc:pt 13269.0 1800) (upc:pt 13269.0 5490) (upc:pt 13269.0 3645.0) (/ pi 2))) (vla-put-stylename o "HAUD-100") (upc:set o "DIM")
 (setq o (vla-adddimrotated ms (upc:pt 12705 6762.0) (upc:pt 14530 6762.0) (upc:pt 13617.5 6762.0) 0)) (vla-put-stylename o "HAUD-100") (upc:set o "DIM")
 (setq o (vla-adddimrotated ms (upc:pt 13920.0 5540) (upc:pt 13920.0 8020) (upc:pt 13920.0 6780.0) (/ pi 2))) (vla-put-stylename o "HAUD-100") (upc:set o "DIM")
 (setq o (vla-adddimrotated ms (upc:pt 6165 2504.0) (upc:pt 10685 2504.0) (upc:pt 8425.0 2504.0) 0)) (vla-put-stylename o "HAUD-100") (upc:set o "DIM")
 (setq o (vla-adddimrotated ms (upc:pt 8946.0 1625) (upc:pt 8946.0 5285) (upc:pt 8946.0 3455.0) (/ pi 2))) (vla-put-stylename o "HAUD-100") (upc:set o "DIM")
 (setq o (vla-adddimrotated ms (upc:pt 6575.0 7303.0) (upc:pt 10575.0 7303.0) (upc:pt 8575.0 7303.0) 0)) (vla-put-stylename o "HAUD-100") (upc:set o "DIM")
 (setq o (vla-adddimrotated ms (upc:pt 8883.0 5285) (upc:pt 8883.0 8460) (upc:pt 8883.0 6872.5) (/ pi 2))) (vla-put-stylename o "HAUD-100") (upc:set o "DIM")
 (setq o (vla-adddimrotated ms (upc:pt 3245 2613.0) (upc:pt 5965 2613.0) (upc:pt 4605.0 2613.0) 0)) (vla-put-stylename o "HAUD-100") (upc:set o "DIM")
 (setq o (vla-adddimrotated ms (upc:pt 5033.0 1625) (upc:pt 5033.0 3915) (upc:pt 5033.0 2770.0) (/ pi 2))) (vla-put-stylename o "HAUD-100") (upc:set o "DIM")
 (setq o (vla-adddimrotated ms (upc:pt 125 2613.0) (upc:pt 3145 2613.0) (upc:pt 1635.0 2613.0) 0)) (vla-put-stylename o "HAUD-100") (upc:set o "DIM")
 (setq o (vla-adddimrotated ms (upc:pt 2190.0 1625) (upc:pt 2190.0 3915) (upc:pt 2190.0 2770.0) (/ pi 2))) (vla-put-stylename o "HAUD-100") (upc:set o "DIM"))))
