(upc:run "C:/temp/cj84a/outputs/cj84A-basic-v010.dwg" "C:/temp/cj84a/operations_v010" "door-901" (quote (lambda (doc / ms o hs) (setq ms (vla-get-modelspace doc)) (upc:set (vla-addline ms (upc:pt 1745.0 4109.5) (upc:pt 1845.0 4109.5)) "DOOR")
 (upc:set (vla-addline ms (upc:pt 1745.0 4909.5) (upc:pt 1845.0 4909.5)) "DOOR")
 (upc:set (vla-addline ms (upc:pt 1745.0 4109.5) (upc:pt 945.0 4109.5)) "DOOR")
 (upc:set (vla-addarc ms (upc:pt 1745.0 4109.5) 800 1.570796 3.141593) "DOOR")
 (upc:set (vla-addline ms (upc:pt 12605.0 5578.5) (upc:pt 12705.0 5578.5)) "DOOR")
 (upc:set (vla-addline ms (upc:pt 12605.0 6378.5) (upc:pt 12705.0 6378.5)) "DOOR")
 (upc:set (vla-addline ms (upc:pt 12605.0 5578.5) (upc:pt 11805.0 5578.5)) "DOOR")
 (upc:set (vla-addarc ms (upc:pt 12605.0 5578.5) 800 1.570796 3.141593) "DOOR")
 (upc:set (vla-addline ms (upc:pt 2480.0 6885.0) (upc:pt 2480.0 7135.0)) "DOOR")
 (upc:set (vla-addline ms (upc:pt 3580.0 6885.0) (upc:pt 3580.0 7135.0)) "DOOR")
 (upc:set (vla-addline ms (upc:pt 3580.0 7135.0) (upc:pt 3580.0 8235.0)) "DOOR")
 (upc:set (vla-addarc ms (upc:pt 3580.0 7135.0) 1100 1.570796 3.141593) "DOOR")
 (upc:set (vla-addline ms (upc:pt 10685.0 4490.0) (upc:pt 10885.0 4490.0)) "DOOR")
 (upc:set (vla-addline ms (upc:pt 10685.0 5390.0) (upc:pt 10885.0 5390.0)) "DOOR")
 (upc:set (vla-addline ms (upc:pt 10885.0 5390.0) (upc:pt 11785.0 5390.0)) "DOOR")
 (upc:set (vla-addarc ms (upc:pt 10885.0 5390.0) 900 -1.570796 0.000000) "DOOR")
 (upc:set (vla-addline ms (upc:pt 4965.0 3915.0) (upc:pt 4965.0 4015.0)) "DOOR")
 (upc:set (vla-addline ms (upc:pt 5865.0 3915.0) (upc:pt 5865.0 4015.0)) "DOOR")
 (upc:set (vla-addline ms (upc:pt 5865.0 3915.0) (upc:pt 5865.0 3015.0)) "DOOR")
 (upc:set (vla-addarc ms (upc:pt 5865.0 3915.0) 900 3.141593 -1.570796) "DOOR")
 (upc:set (vla-addline ms (upc:pt 2145.0 3915.0) (upc:pt 2145.0 4015.0)) "DOOR")
 (upc:set (vla-addline ms (upc:pt 3045.0 3915.0) (upc:pt 3045.0 4015.0)) "DOOR")
 (upc:set (vla-addline ms (upc:pt 3045.0 3915.0) (upc:pt 3045.0 3015.0)) "DOOR")
 (upc:set (vla-addarc ms (upc:pt 3045.0 3915.0) 900 3.141593 -1.570796) "DOOR")
 (upc:set (vla-addline ms (upc:pt 4940.0 5235.0) (upc:pt 4940.0 5335.0)) "DOOR")
 (upc:set (vla-addline ms (upc:pt 5740.0 5235.0) (upc:pt 5740.0 5335.0)) "DOOR")
 (upc:set (vla-addline ms (upc:pt 4940.0 5335.0) (upc:pt 4940.0 6135.0)) "DOOR")
 (upc:set (vla-addarc ms (upc:pt 4940.0 5335.0) 800 0.000000 1.570796) "DOOR")
 (upc:set (vla-addline ms (upc:pt 12720.0 790.0) (upc:pt 12840.0 790.0)) "DOOR")
 (upc:set (vla-addline ms (upc:pt 12720.0 1540.0) (upc:pt 12840.0 1540.0)) "DOOR")
 (upc:set (upc:pline ms '((12735.0 790.0) (12735.0 1215.0) (12775.0 1215.0) (12775.0 790.0)) t) "DOOR")
 (upc:set (upc:pline ms '((12785.0 1115.0) (12785.0 1540.0) (12825.0 1540.0) (12825.0 1115.0)) t) "DOOR"))))
