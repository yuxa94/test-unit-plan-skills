(upc:run "C:/temp/cj84a/outputs/cj84A-basic-v007.dwg" "C:/temp/cj84a/operations_v007" "win-601" (quote (lambda (doc / ms o hs) (setq ms (vla-get-modelspace doc)) (upc:set (upc:pline ms '((6625.0 1325.0) (10225.0 1325.0) (10225.0 1515.0) (6625.0 1515.0)) t) "WIN")
 (upc:set (vla-addline ms (upc:pt 6625.0 1391.5) (upc:pt 10225.0 1391.5)) "WIN")
 (upc:set (vla-addline ms (upc:pt 6625.0 1448.5) (upc:pt 10225.0 1448.5)) "WIN")
 (upc:set (upc:pline ms '((11025.0 1500.0) (12525.0 1500.0) (12525.0 1690.0) (11025.0 1690.0)) t) "WIN")
 (upc:set (vla-addline ms (upc:pt 11025.0 1566.5) (upc:pt 12525.0 1566.5)) "WIN")
 (upc:set (vla-addline ms (upc:pt 11025.0 1623.5) (upc:pt 12525.0 1623.5)) "WIN")
 (upc:set (upc:pline ms '((3725.0 1325.0) (5525.0 1325.0) (5525.0 1515.0) (3725.0 1515.0)) t) "WIN")
 (upc:set (vla-addline ms (upc:pt 3725.0 1391.5) (upc:pt 5525.0 1391.5)) "WIN")
 (upc:set (vla-addline ms (upc:pt 3725.0 1448.5) (upc:pt 5525.0 1448.5)) "WIN")
 (upc:set (upc:pline ms '((675.0 1325.0) (2475.0 1325.0) (2475.0 1515.0) (675.0 1515.0)) t) "WIN")
 (upc:set (vla-addline ms (upc:pt 675.0 1391.5) (upc:pt 2475.0 1391.5)) "WIN")
 (upc:set (vla-addline ms (upc:pt 675.0 1448.5) (upc:pt 2475.0 1448.5)) "WIN")
 (upc:set (upc:pline ms '((7450.0 8570.0) (8950.0 8570.0) (8950.0 8760.0) (7450.0 8760.0)) t) "WIN")
 (upc:set (vla-addline ms (upc:pt 7450.0 8636.5) (upc:pt 8950.0 8636.5)) "WIN")
 (upc:set (vla-addline ms (upc:pt 7450.0 8693.5) (upc:pt 8950.0 8693.5)) "WIN")
 (upc:set (upc:pline ms '((13115.0 8130.0) (14115.0 8130.0) (14115.0 8330.0) (13115.0 8330.0)) t) "WIN")
 (upc:set (vla-addline ms (upc:pt 13115.0 8200.0) (upc:pt 14115.0 8200.0)) "WIN")
 (upc:set (vla-addline ms (upc:pt 13115.0 8260.0) (upc:pt 14115.0 8260.0)) "WIN")
 (upc:set (upc:pline ms '((13225.0 0.0) (14225.0 0.0) (14225.0 200.0) (13225.0 200.0)) t) "WIN")
 (upc:set (vla-addline ms (upc:pt 13225.0 100.0) (upc:pt 14225.0 100.0)) "WIN"))))
