(upc:run "C:/temp/cj84a/outputs/cj84A-basic-v005.dwg" "C:/temp/cj84a/operations_v005" "win-401" (quote (lambda (doc / ms o hs) (setq ms (vla-get-modelspace doc)) (upc:set (upc:pline ms '((6625.0 1325.0) (10225.0 1325.0) (10225.0 1515.0) (6625.0 1515.0)) t) "WIN")
 (upc:set (vla-addline ms (upc:pt 6625.0 1391.5) (upc:pt 10225.0 1391.5)) "WIN")
 (upc:set (vla-addline ms (upc:pt 6625.0 1448.5) (upc:pt 10225.0 1448.5)) "WIN")
 (upc:set (upc:pline ms '((14685.0 2725.0) (14685.0 4525.0) (14935.0 4525.0) (14935.0 2725.0)) t) "WIN")
 (upc:set (vla-addline ms (upc:pt 14772.5 2725.0) (upc:pt 14772.5 4525.0)) "WIN")
 (upc:set (vla-addline ms (upc:pt 14847.5 2725.0) (upc:pt 14847.5 4525.0)) "WIN")
 (upc:set (upc:pline ms '((3725.0 1325.0) (5525.0 1325.0) (5525.0 1515.0) (3725.0 1515.0)) t) "WIN")
 (upc:set (vla-addline ms (upc:pt 3725.0 1391.5) (upc:pt 5525.0 1391.5)) "WIN")
 (upc:set (vla-addline ms (upc:pt 3725.0 1448.5) (upc:pt 5525.0 1448.5)) "WIN")
 (upc:set (upc:pline ms '((675.0 1325.0) (2475.0 1325.0) (2475.0 1515.0) (675.0 1515.0)) t) "WIN")
 (upc:set (vla-addline ms (upc:pt 675.0 1391.5) (upc:pt 2475.0 1391.5)) "WIN")
 (upc:set (vla-addline ms (upc:pt 675.0 1448.5) (upc:pt 2475.0 1448.5)) "WIN")
 (upc:set (upc:pline ms '((7300.0 8570.0) (9100.0 8570.0) (9100.0 8760.0) (7300.0 8760.0)) t) "WIN")
 (upc:set (vla-addline ms (upc:pt 7300.0 8636.5) (upc:pt 9100.0 8636.5)) "WIN")
 (upc:set (vla-addline ms (upc:pt 7300.0 8693.5) (upc:pt 9100.0 8693.5)) "WIN")
 (upc:set (upc:pline ms '((14685.0 5950.0) (14685.0 7750.0) (14935.0 7750.0) (14935.0 5950.0)) t) "WIN")
 (upc:set (vla-addline ms (upc:pt 14772.5 5950.0) (upc:pt 14772.5 7750.0)) "WIN")
 (upc:set (vla-addline ms (upc:pt 14847.5 5950.0) (upc:pt 14847.5 7750.0)) "WIN")
 (upc:set (upc:pline ms '((13225.0 0.0) (14225.0 0.0) (14225.0 200.0) (13225.0 200.0)) t) "WIN")
 (upc:set (vla-addline ms (upc:pt 13225.0 100.0) (upc:pt 14225.0 100.0)) "WIN"))))
