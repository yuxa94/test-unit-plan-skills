(upc:run "C:/temp/cj84a/outputs/cj84A-basic-v008chk.dwg" "C:/temp/cj84a/operations_v008chk" "wall-701" (quote (lambda (doc / ms o hs) (setq ms (vla-get-modelspace doc)) (setq o (upc:set (upc:pline ms '((-125.0 0.0) (13225.0 0.0) (13225.0 200.0) (12840.0 200.0) (12840.0 790.0) (12720.0 790.0) (12720.0 200.0) (125.0 200.0) (125.0 3915.0) (1955.0 3915.0) (1955.0 4115.0) (1850.0 4115.0) (1850.0 4109.5) (1740.0 4109.5) (1740.0 4115.0) (125.0 4115.0) (125.0 7025.0) (1605.0 7025.0) (1605.0 6885.0) (2480.0 6885.0) (2480.0 7135.0) (1955.0 7135.0) (1955.0 7275.0) (-125.0 7275.0)) t) "CONC") hs nil)
 (setq o (upc:set (upc:pline ms '((3580.0 6885.0) (6228.0 6885.0) (6228.0 6792.1) (6265.0 6792.1) (6265.0 5235.0) (6465.0 5235.0) (6465.0 7375.0) (6452.0 7375.0) (6452.0 8875.0) (6575.0 8875.0) (6575.0 9125.0) (6452.0 9125.0) (6452.0 10135.0) (10685.0 10135.0) (10685.0 8330.0) (9775.0 8330.0) (9775.0 8130.0) (10685.0 8130.0) (10685.0 5390.0) (10885.0 5390.0) (10885.0 8130.0) (12815.0 8130.0) (12815.0 8330.0) (10885.0 8330.0) (10885.0 10135.0) (12455.0 10135.0) (12455.0 9545.0) (14685.0 9545.0) (14685.0 1690.0) (12705.0 1690.0) (12705.0 1490.0) (12715.0 1490.0) (12715.0 1540.0) (12845.0 1540.0) (12845.0 1490.0) (14685.0 1490.0) (14685.0 200.0) (14225.0 200.0) (14225.0 0.0) (14935.0 0.0) (14935.0 9745.0) (12655.0 9745.0) (12655.0 10135.0) (12705.0 10135.0) (12705.0 10335.0) (5445.0 10335.0) (5445.0 8875.0) (6228.0 8875.0) (6228.0 7135.0) (3580.0 7135.0)) t) "CONC") hs nil)
 (setq hs (cons (list (upc:set (upc:pline ms '((5695.0 9125.0) (5695.0 10135.0) (6228.0 10135.0) (6228.0 9125.0)) t) "CONC")) hs))
 (setq o (upc:set (upc:pline ms '((5965.0 1325.0) (6165.0 1325.0) (6165.0 4015.0) (5965.0 4015.0)) t) "CONC") hs nil)
 (setq o (upc:set (upc:pline ms '((10685.0 1325.0) (10885.0 1325.0) (10885.0 4490.0) (10685.0 4490.0)) t) "CONC") hs nil)
 (setq o (upc:set (upc:pline ms '((125.0 1325.0) (675.0 1325.0) (675.0 1515.0) (125.0 1515.0)) t) "WAL") hs nil)
 (upc:set (upc:hatch ms "ANSI31" 10 0 (list o) hs) "A_HAT")
 (setq o (upc:set (upc:pline ms '((2475.0 1325.0) (3725.0 1325.0) (3725.0 1515.0) (2475.0 1515.0)) t) "WAL") hs nil)
 (upc:set (upc:hatch ms "ANSI31" 10 0 (list o) hs) "A_HAT")
 (setq o (upc:set (upc:pline ms '((5525.0 1325.0) (5965.0 1325.0) (5965.0 1515.0) (5525.0 1515.0)) t) "WAL") hs nil)
 (upc:set (upc:hatch ms "ANSI31" 10 0 (list o) hs) "A_HAT")
 (setq o (upc:set (upc:pline ms '((5975.0 8570.0) (6228.0 8570.0) (6228.0 8760.0) (5975.0 8760.0)) t) "WAL") hs nil)
 (upc:set (upc:hatch ms "ANSI31" 10 0 (list o) hs) "A_HAT")
 (setq o (upc:set (upc:pline ms '((6165.0 1325.0) (6625.0 1325.0) (6625.0 1515.0) (6165.0 1515.0)) t) "WAL") hs nil)
 (upc:set (upc:hatch ms "ANSI31" 10 0 (list o) hs) "A_HAT")
 (setq o (upc:set (upc:pline ms '((6452.0 8570.0) (7450.0 8570.0) (7450.0 8760.0) (6452.0 8760.0)) t) "WAL") hs nil)
 (upc:set (upc:hatch ms "ANSI31" 10 0 (list o) hs) "A_HAT")
 (setq o (upc:set (upc:pline ms '((8950.0 8570.0) (10065.0 8570.0) (10065.0 8330.0) (10255.0 8330.0) (10255.0 8570.0) (10375.0 8570.0) (10375.0 8760.0) (10255.0 8760.0) (10255.0 10135.0) (10065.0 10135.0) (10065.0 8760.0) (8950.0 8760.0)) t) "WAL") hs nil)
 (upc:set (upc:hatch ms "ANSI31" 10 0 (list o) hs) "A_HAT")
 (setq o (upc:set (upc:pline ms '((10065.0 7950.0) (10255.0 7950.0) (10255.0 8130.0) (10065.0 8130.0)) t) "WAL") hs nil)
 (upc:set (upc:hatch ms "ANSI31" 10 0 (list o) hs) "A_HAT")
 (setq o (upc:set (upc:pline ms '((10225.0 1325.0) (10685.0 1325.0) (10685.0 1690.0) (10575.0 1690.0) (10575.0 1515.0) (10225.0 1515.0)) t) "WAL") hs nil)
 (upc:set (upc:hatch ms "ANSI31" 10 0 (list o) hs) "A_HAT")
 (setq o (upc:set (upc:pline ms '((10885.0 1325.0) (10995.0 1325.0) (10995.0 1500.0) (11025.0 1500.0) (11025.0 1690.0) (10885.0 1690.0)) t) "WAL") hs nil)
 (upc:set (upc:hatch ms "ANSI31" 10 0 (list o) hs) "A_HAT")
 (setq o (upc:set (upc:pline ms '((12525.0 1500.0) (12705.0 1500.0) (12705.0 1690.0) (12525.0 1690.0)) t) "WAL") hs nil)
 (upc:set (upc:hatch ms "ANSI31" 10 0 (list o) hs) "A_HAT")
 (setq o (upc:set (upc:pline ms '((12815.0 8130.0) (13115.0 8130.0) (13115.0 8330.0) (12815.0 8330.0)) t) "WAL") hs nil)
 (upc:set (upc:hatch ms "ANSI31" 10 0 (list o) hs) "A_HAT")
 (setq o (upc:set (upc:pline ms '((14115.0 8130.0) (14685.0 8130.0) (14685.0 8330.0) (14115.0 8330.0)) t) "WAL") hs nil)
 (upc:set (upc:hatch ms "ANSI31" 10 0 (list o) hs) "A_HAT")
 (setq o (upc:set (upc:pline ms '((125.0 6375.0) (1745.0 6375.0) (1745.0 4909.5) (1845.0 4909.5) (1845.0 6885.0) (1745.0 6885.0) (1745.0 6475.0) (125.0 6475.0)) t) "WAL_DRY") hs nil)
 (setq o (upc:set (upc:pline ms '((1955.0 3915.0) (2145.0 3915.0) (2145.0 4015.0) (1955.0 4015.0)) t) "WAL_DRY") hs nil)
 (setq o (upc:set (upc:pline ms '((3045.0 3915.0) (3145.0 3915.0) (3145.0 1515.0) (3245.0 1515.0) (3245.0 3915.0) (4965.0 3915.0) (4965.0 4015.0) (3045.0 4015.0)) t) "WAL_DRY") hs nil)
 (setq o (upc:set (upc:pline ms '((4265.0 5235.0) (4940.0 5235.0) (4940.0 5335.0) (4365.0 5335.0) (4365.0 6885.0) (4265.0 6885.0)) t) "WAL_DRY") hs nil)
 (setq o (upc:set (upc:pline ms '((5740.0 5235.0) (6265.0 5235.0) (6265.0 5335.0) (5740.0 5335.0)) t) "WAL_DRY") hs nil)
 (setq o (upc:set (upc:pline ms '((5865.0 3915.0) (5965.0 3915.0) (5965.0 4015.0) (5865.0 4015.0)) t) "WAL_DRY") hs nil)
 (setq o (upc:set (upc:pline ms '((10885.0 5490.0) (12705.0 5490.0) (12705.0 5578.5) (12600.0 5578.5) (12600.0 5590.0) (10885.0 5590.0)) t) "WAL_DRY") hs nil)
 (setq o (upc:set (upc:pline ms '((10885.0 7070.0) (11395.0 7070.0) (11395.0 8130.0) (11320.0 8130.0) (11320.0 7145.0) (10885.0 7145.0)) t) "WAL_DRY") hs nil)
 (setq o (upc:set (upc:pline ms '((11320.0 8330.0) (11395.0 8330.0) (11395.0 10135.0) (11320.0 10135.0)) t) "WAL_DRY") hs nil)
 (setq o (upc:set (upc:pline ms '((12605.0 6378.5) (12705.0 6378.5) (12705.0 8130.0) (12605.0 8130.0)) t) "WAL_DRY") hs nil)
 (setq o (upc:set (upc:pline ms '((12605.0 8330.0) (12705.0 8330.0) (12705.0 9545.0) (12605.0 9545.0)) t) "WAL_DRY") hs nil)
 (setq o (upc:set (upc:pline ms '((12655.0 9745.0) (12705.0 9745.0) (12705.0 10135.0) (12655.0 10135.0)) t) "WAL_DRY") hs nil)
 (setq o (upc:set (upc:pline ms '((13905.0 5490.0) (14685.0 5490.0) (14685.0 5590.0) (13905.0 5590.0)) t) "WAL_DRY") hs nil)
 (upc:set (vla-addline ms (upc:pt 12640.0 5490.0) (upc:pt 12640.0 10335.0)) "CEN_WALL")
 (upc:set (vla-addline ms (upc:pt 12465.0 8145.0) (upc:pt 14935.0 8145.0)) "CEN_WALL")
 (upc:set (vla-addline ms (upc:pt 9775.0 8140.0) (upc:pt 12815.0 8140.0)) "CEN_CON")
 (upc:set (vla-addline ms (upc:pt 12455.0 9745.0) (upc:pt 14935.0 9745.0)) "CEN_CON")
 (upc:set (vla-addline ms (upc:pt 13905.0 5540.0) (upc:pt 14935.0 5540.0)) "CEN_WALL")
 (upc:set (vla-addline ms (upc:pt 5570.0 8875.0) (upc:pt 5570.0 10335.0)) "CEN_CON")
 (upc:set (vla-addline ms (upc:pt 1780.0 3915.0) (upc:pt 1780.0 7135.0)) "CEN_WALL")
 (upc:set (vla-addline ms (upc:pt 5445.0 9000.0) (upc:pt 6575.0 9000.0)) "CEN_CON")
 (upc:set (vla-addline ms (upc:pt 6340.0 6792.1) (upc:pt 6340.0 10335.0)) "CEN_CON")
 (upc:set (vla-addline ms (upc:pt 12555.0 9545.0) (upc:pt 12555.0 10335.0)) "CEN_CON")
 (upc:set (vla-addline ms (upc:pt 6365.0 5235.0) (upc:pt 6365.0 7375.0)) "CEN_CON")
 (upc:set (vla-addline ms (upc:pt 12705.0 1680.0) (upc:pt 14935.0 1680.0)) "CEN_CON")
 (upc:set (vla-addline ms (upc:pt 5975.0 8585.0) (upc:pt 10375.0 8585.0)) "CEN_WALL")
 (upc:set (vla-addline ms (upc:pt 10080.0 7950.0) (upc:pt 10080.0 10335.0)) "CEN_WALL")
 (upc:set (vla-addline ms (upc:pt 11390.0 7070.0) (upc:pt 11390.0 10335.0)) "CEN_WALL")
 (upc:set (vla-addline ms (upc:pt 10685.0 7090.0) (upc:pt 11395.0 7090.0)) "CEN_WALL")
 (upc:set (vla-addline ms (upc:pt 12780.0 0.0) (upc:pt 12780.0 1690.0)) "CEN_CON")
 (upc:set (vla-addline ms (upc:pt -125.0 1500.0) (upc:pt 10995.0 1500.0)) "CEN_WALL")
 (upc:set (vla-addline ms (upc:pt -125.0 4035.0) (upc:pt 1955.0 4035.0)) "CEN_CON")
 (upc:set (vla-addline ms (upc:pt 10785.0 1325.0) (upc:pt 10785.0 10335.0)) "CEN_CON")
 (upc:set (vla-addline ms (upc:pt 14630.0 0.0) (upc:pt 14630.0 9745.0)) "CEN_CON")
 (upc:set (vla-addline ms (upc:pt 10575.0 1675.0) (upc:pt 12880.0 1675.0)) "CEN_WALL")
 (upc:set (vla-addline ms (upc:pt 0.0 0.0) (upc:pt 14935.0 0.0)) "CEN_CON")
 (upc:set (vla-addline ms (upc:pt 10685.0 5555.0) (upc:pt 12705.0 5555.0)) "CEN_WALL")
 (upc:set (vla-addline ms (upc:pt 4265.0 5285.0) (upc:pt 6465.0 5285.0)) "CEN_WALL")
 (upc:set (vla-addline ms (upc:pt 6065.0 1325.0) (upc:pt 6065.0 4015.0)) "CEN_CON")
 (upc:set (vla-addline ms (upc:pt 1605.0 3965.0) (upc:pt 6165.0 3965.0)) "CEN_WALL")
 (upc:set (vla-addline ms (upc:pt 3195.0 1325.0) (upc:pt 3195.0 4015.0)) "CEN_WALL")
 (upc:set (vla-addline ms (upc:pt 0.0 0.0) (upc:pt 0.0 7275.0)) "CEN_CON")
 (upc:set (vla-addline ms (upc:pt 1605.0 7010.0) (upc:pt 6465.0 7010.0)) "CEN_CON")
 (upc:set (vla-addline ms (upc:pt 4315.0 5235.0) (upc:pt 4315.0 7135.0)) "CEN_WALL")
 (upc:set (vla-addline ms (upc:pt -125.0 7150.0) (upc:pt 1955.0 7150.0)) "CEN_CON")
 (upc:set (vla-addline ms (upc:pt -125.0 6425.0) (upc:pt 1845.0 6425.0)) "CEN_WALL")
 (upc:set (vla-addline ms (upc:pt 5445.0 10335.0) (upc:pt 12705.0 10335.0)) "CEN_CON"))))
