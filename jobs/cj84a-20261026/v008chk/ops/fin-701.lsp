(upc:run "C:/temp/cj84a/outputs/cj84A-basic-v008chk.dwg" "C:/temp/cj84a/operations_v008chk" "fin-701" (quote (lambda (doc / ms o h) (setq ms (vla-get-modelspace doc)) (upc:set (upc:pline ms '((10885.0 1800.0) (14489.0 1800.0) (14489.0 1690.0) (14530.0 1690.0) (14530.0 5490.0) (13905.0 5490.0) (13905.0 5540.0) (12705.0 5540.0) (12705.0 5490.0) (10885.0 5490.0)) t) "FIN")
 (upc:set (upc:pline ms '((12705.0 5540.0) (13905.0 5540.0) (13905.0 5590.0) (14530.0 5590.0) (14530.0 8120.8) (14630.0 8120.8) (14630.0 8130.0) (14523.3 8130.0) (14523.3 8020.0) (12705.0 8020.0)) t) "FIN")
 (upc:set (upc:pline ms '((10885.0 5590.0) (12605.0 5590.0) (12605.0 8020.0) (11512.1 8020.0) (11512.1 8130.0) (11395.0 8130.0) (11395.0 7070.0) (10885.0 7070.0)) t) "FIN")
 (upc:set (upc:pline ms '((4315.0 4015.0) (6165.0 4015.0) (6165.0 1625.0) (10575.0 1625.0) (10575.0 1800.0) (10685.0 1800.0) (10685.0 5285.0) (6465.0 5285.0) (6465.0 5235.0) (4315.0 5235.0)) t) "FIN")
 (upc:set (upc:pline ms '((6465.0 5285.0) (10685.0 5285.0) (10685.0 7058.6) (10575.0 7058.6) (10575.0 8020.0) (10255.0 8020.0) (10255.0 7950.0) (9955.0 7950.0) (9955.0 8130.0) (9775.0 8130.0) (9775.0 8330.0) (9955.0 8330.0) (9955.0 8427.0) (10065.0 8427.0) (10065.0 8570.0) (9975.0 8570.0) (9975.0 8460.0) (6562.0 8460.0) (6562.0 7375.0) (6575.0 7375.0) (6575.0 6947.0) (6562.0 6947.0) (6562.0 6792.1) (6465.0 6792.1)) t) "FIN")
 (upc:set (upc:pline ms '((4365.0 5335.0) (6265.0 5335.0) (6265.0 6775.0) (4365.0 6775.0)) t) "FIN")
 (upc:set (upc:pline ms '((1845.0 4115.0) (1955.0 4115.0) (1955.0 4015.0) (4315.0 4015.0) (4315.0 5235.0) (4265.0 5235.0) (4265.0 6775.0) (1845.0 6775.0)) t) "FIN")
 (upc:set (upc:pline ms '((3245.0 1625.0) (5965.0 1625.0) (5965.0 3915.0) (3245.0 3915.0)) t) "FIN")
 (upc:set (upc:pline ms '((125.0 1625.0) (3145.0 1625.0) (3145.0 3915.0) (125.0 3915.0)) t) "FIN")
 (upc:set (upc:pline ms '((125.0 200.0) (12720.0 200.0) (12720.0 1490.0) (12705.0 1490.0) (12705.0 1500.0) (10995.0 1500.0) (10995.0 1325.0) (125.0 1325.0)) t) "FIN")
 (upc:set (upc:pline ms '((12840.0 200.0) (14630.0 200.0) (14630.0 1490.0) (12840.0 1490.0)) t) "FIN")
 (upc:set (upc:pline ms '((10885.0 8330.0) (11320.0 8330.0) (11320.0 10135.0) (10885.0 10135.0)) t) "FIN")
 (upc:set (upc:pline ms '((11395.0 8330.0) (12605.0 8330.0) (12605.0 9545.0) (12455.0 9545.0) (12455.0 10135.0) (11395.0 10135.0)) t) "FIN")
 (upc:set (upc:pline ms '((12705.0 8330.0) (14685.0 8330.0) (14685.0 9545.0) (12705.0 9545.0)) t) "FIN")
 (upc:set (upc:pline ms '((12705.0 9745.0) (14685.0 9745.0) (14685.0 10335.0) (12705.0 10335.0)) t) "FIN")
 (upc:set (upc:pline ms '((125.0 4115.0) (1745.0 4115.0) (1745.0 6375.0) (125.0 6375.0)) t) "FIN")
 (upc:set (upc:pline ms '((6452.0 8760.0) (10065.0 8760.0) (10065.0 10135.0) (6452.0 10135.0) (6452.0 9125.0) (6575.0 9125.0) (6575.0 8875.0) (6452.0 8875.0)) t) "FIN")
 (setq o (upc:pline ms '((125.0 200.0) (12720.0 200.0) (12720.0 1490.0) (12705.0 1490.0) (12705.0 1500.0) (10995.0 1500.0) (10995.0 1325.0) (125.0 1325.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((12840.0 200.0) (14630.0 200.0) (14630.0 1490.0) (12840.0 1490.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((10885.0 8330.0) (11320.0 8330.0) (11320.0 10135.0) (10885.0 10135.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((11395.0 8330.0) (12605.0 8330.0) (12605.0 9545.0) (12455.0 9545.0) (12455.0 10135.0) (11395.0 10135.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((12705.0 8330.0) (14685.0 8330.0) (14685.0 9545.0) (12705.0 9545.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((12705.0 9745.0) (14685.0 9745.0) (14685.0 10335.0) (12705.0 10335.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((6452.0 8760.0) (10065.0 8760.0) (10065.0 10135.0) (6452.0 10135.0) (6452.0 9125.0) (6575.0 9125.0) (6575.0 8875.0) (6452.0 8875.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일"))))
