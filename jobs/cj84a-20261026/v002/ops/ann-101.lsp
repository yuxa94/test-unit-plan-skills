(upc:run "C:/temp/cj84a/outputs/cj84A-basic-v002.dwg" "C:/temp/cj84a/operations_v002" "ann-101" (quote (lambda (doc / ms o) (setq ms (vla-get-modelspace doc)) (setq o (vla-addtext ms "침실1" (upc:pt 12519.0 4047.0) 120)) (vla-put-stylename o "HAUD01") (upc:set o "실명")
 (setq o (vla-addtext ms "드레스룸" (upc:pt 13170.0 7062.0) 120)) (vla-put-stylename o "HAUD01") (upc:set o "실명")
 (setq o (vla-addtext ms "욕실2" (upc:pt 11692.0 6573.0) 120)) (vla-put-stylename o "HAUD01") (upc:set o "실명")
 (setq o (vla-addtext ms "거실" (upc:pt 8196.0 2804.0) 120)) (vla-put-stylename o "HAUD01") (upc:set o "실명")
 (setq o (vla-addtext ms "주방/식당" (upc:pt 8133.0 7603.0) 120)) (vla-put-stylename o "HAUD01") (upc:set o "실명")
 (setq o (vla-addtext ms "팬트리" (upc:pt 4976.0 6118.0) 120)) (vla-put-stylename o "HAUD01") (upc:set o "실명")
 (setq o (vla-addtext ms "현관" (upc:pt 2653.0 6154.0) 120)) (vla-put-stylename o "HAUD01") (upc:set o "실명")
 (setq o (vla-addtext ms "침실2" (upc:pt 4283.0 2913.0) 120)) (vla-put-stylename o "HAUD01") (upc:set o "실명")
 (setq o (vla-addtext ms "침실3" (upc:pt 1440.0 2913.0) 120)) (vla-put-stylename o "HAUD01") (upc:set o "실명")
 (setq o (vla-addtext ms "발코니1" (upc:pt 6185.0 859.0) 120)) (vla-put-stylename o "HAUD01") (upc:set o "실명")
 (setq o (vla-addtext ms "하향식피난구" (upc:pt 13236.0 855.0) 120)) (vla-put-stylename o "HAUD01") (upc:set o "실명")
 (setq o (vla-addtext ms "발코니2" (upc:pt 11290.0 9283.0) 120)) (vla-put-stylename o "HAUD01") (upc:set o "실명")
 (setq o (vla-addtext ms "ELEV. 홀" (upc:pt 261.0 8183.0) 120)) (vla-put-stylename o "HAUD01") (upc:set o "실명")
 (setq o (vla-addtext ms "욕실1" (upc:pt 689.0 5120.0) 120)) (vla-put-stylename o "HAUD01") (upc:set o "실명"))))
