(upc:run "C:/temp/cj84a/outputs/cj84A-basic-v001.dwg" "C:/temp/cj84a/operations" "ins-002" (quote (lambda (doc / ms o hs old) (setq ms (vla-get-modelspace doc)) (setq old nil) (vlax-for e ms (if (= (vla-get-layer e) "INS") (setq old (cons e old)))) (foreach e old (vla-delete e))
 (setq o (upc:set (upc:pline ms '((6452.0 8415.0) (7175.0 8415.0) (7175.0 8570.0) (6452.0 8570.0)) t) "INS") hs nil)
 (upc:set (upc:hatch ms "DASH" 10 0 (list o) hs) "INS")
 (setq o (upc:set (upc:pline ms '((8675.0 8415.0) (9975.0 8415.0) (9975.0 8570.0) (8675.0 8570.0)) t) "INS") hs nil)
 (upc:set (upc:hatch ms "DASH" 10 0 (list o) hs) "INS")
 (setq o (upc:set (upc:pline ms '((11512.1 7975.0) (12605.0 7975.0) (12605.0 8130.0) (11512.1 8130.0)) t) "INS") hs nil)
 (upc:set (upc:hatch ms "DASH" 10 0 (list o) hs) "INS")
 (setq o (upc:set (upc:pline ms '((12705.0 7975.0) (13105.0 7975.0) (13105.0 8130.0) (12705.0 8130.0)) t) "INS") hs nil)
 (upc:set (upc:hatch ms "DASH" 10 0 (list o) hs) "INS")
 (setq o (upc:set (upc:pline ms '((14105.0 7975.0) (14523.3 7975.0) (14523.3 8130.0) (14105.0 8130.0)) t) "INS") hs nil)
 (upc:set (upc:hatch ms "DASH" 10 0 (list o) hs) "INS")
 (setq o (upc:set (upc:pline ms '((14530.0 1690.0) (14685.0 1690.0) (14685.0 5490.0) (14530.0 5490.0)) t) "INS") hs nil)
 (upc:set (upc:hatch ms "DASH" 10 0 (list o) hs) "INS")
 (setq o (upc:set (upc:pline ms '((14530.0 5590.0) (14685.0 5590.0) (14685.0 8120.8) (14530.0 8120.8)) t) "INS") hs nil)
 (upc:set (upc:hatch ms "DASH" 10 0 (list o) hs) "INS")
 (setq o (upc:set (upc:pline ms '((125.0 1515.0) (735.0 1515.0) (735.0 1625.0) (125.0 1625.0)) t) "INS") hs nil)
 (upc:set (upc:hatch ms "DASH" 10 0 (list o) hs) "INS")
 (setq o (upc:set (upc:pline ms '((1605.0 6775.0) (1745.0 6775.0) (1745.0 6885.0) (1605.0 6885.0)) t) "INS") hs nil)
 (upc:set (upc:hatch ms "DASH" 10 0 (list o) hs) "INS")
 (setq o (upc:set (upc:pline ms '((1845.0 6775.0) (2335.0 6775.0) (2335.0 6885.0) (1845.0 6885.0)) t) "INS") hs nil)
 (upc:set (upc:hatch ms "DASH" 10 0 (list o) hs) "INS")
 (setq o (upc:set (upc:pline ms '((2535.0 1515.0) (3145.0 1515.0) (3145.0 1625.0) (2535.0 1625.0)) t) "INS") hs nil)
 (upc:set (upc:hatch ms "DASH" 10 0 (list o) hs) "INS")
 (setq o (upc:set (upc:pline ms '((3245.0 1515.0) (3705.0 1515.0) (3705.0 1625.0) (3245.0 1625.0)) t) "INS") hs nil)
 (upc:set (upc:hatch ms "DASH" 10 0 (list o) hs) "INS")
 (setq o (upc:set (upc:pline ms '((3455.0 6775.0) (4265.0 6775.0) (4265.0 6885.0) (3455.0 6885.0)) t) "INS") hs nil)
 (upc:set (upc:hatch ms "DASH" 10 0 (list o) hs) "INS")
 (setq o (upc:set (upc:pline ms '((4365.0 6775.0) (6265.0 6775.0) (6265.0 6792.1) (6228.0 6792.1) (6228.0 6885.0) (4365.0 6885.0)) t) "INS") hs nil)
 (upc:set (upc:hatch ms "DASH" 10 0 (list o) hs) "INS")
 (setq o (upc:set (upc:pline ms '((5505.0 1515.0) (5965.0 1515.0) (5965.0 1625.0) (5505.0 1625.0)) t) "INS") hs nil)
 (upc:set (upc:hatch ms "DASH" 10 0 (list o) hs) "INS")
 (setq o (upc:set (upc:pline ms '((6165.0 1515.0) (6625.0 1515.0) (6625.0 1625.0) (6165.0 1625.0)) t) "INS") hs nil)
 (upc:set (upc:hatch ms "DASH" 10 0 (list o) hs) "INS")
 (setq o (upc:set (upc:pline ms '((6452.0 7375.0) (6465.0 7375.0) (6465.0 6792.1) (6562.0 6792.1) (6562.0 6947.0) (6575.0 6947.0) (6575.0 7375.0) (6562.0 7375.0) (6562.0 8563.5) (6452.0 8563.5)) t) "INS") hs nil)
 (upc:set (upc:hatch ms "DASH" 10 0 (list o) hs) "INS")
 (setq o (upc:set (upc:pline ms '((9955.0 7950.0) (10065.0 7950.0) (10065.0 8130.0) (9955.0 8130.0)) t) "INS") hs nil)
 (upc:set (upc:hatch ms "DASH" 10 0 (list o) hs) "INS")
 (setq o (upc:set (upc:pline ms '((9955.0 8330.0) (10065.0 8330.0) (10065.0 8427.0) (9955.0 8427.0)) t) "INS") hs nil)
 (upc:set (upc:hatch ms "DASH" 10 0 (list o) hs) "INS")
 (setq o (upc:set (upc:pline ms '((10225.0 1515.0) (10575.0 1515.0) (10575.0 1625.0) (10225.0 1625.0)) t) "INS") hs nil)
 (upc:set (upc:hatch ms "DASH" 10 0 (list o) hs) "INS")
 (setq o (upc:set (upc:pline ms '((10255.0 8020.0) (10575.0 8020.0) (10575.0 7058.6) (10685.0 7058.6) (10685.0 8130.0) (10255.0 8130.0)) t) "INS") hs nil)
 (upc:set (upc:hatch ms "DASH" 10 0 (list o) hs) "INS")
 (setq o (upc:set (upc:pline ms '((10575.0 1690.0) (10685.0 1690.0) (10685.0 1800.0) (10575.0 1800.0)) t) "INS") hs nil)
 (upc:set (upc:hatch ms "DASH" 10 0 (list o) hs) "INS")
 (setq o (upc:set (upc:pline ms '((10885.0 1690.0) (11220.0 1690.0) (11220.0 1800.0) (10885.0 1800.0)) t) "INS") hs nil)
 (upc:set (upc:hatch ms "DASH" 10 0 (list o) hs) "INS")
 (setq o (upc:set (upc:pline ms '((12720.0 1690.0) (14489.0 1690.0) (14489.0 1800.0) (12720.0 1800.0)) t) "INS") hs nil)
 (upc:set (upc:hatch ms "DASH" 10 0 (list o) hs) "INS"))))
