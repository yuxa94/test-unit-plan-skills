(upc:run "C:/temp/cj84a/outputs/cj84A-basic-v001.dwg" "C:/temp/cj84a/operations" "wall-001" (quote (lambda (doc / ms o hs) (setq ms (vla-get-modelspace doc)) (setq o (upc:set (upc:pline ms '((-125.0 0.0) (13170.0 0.0) (13170.0 200.0) (12840.0 200.0) (12840.0 720.0) (12720.0 720.0) (12720.0 200.0) (125.0 200.0) (125.0 3915.0) (1955.0 3915.0) (1955.0 4115.0) (125.0 4115.0) (125.0 7025.0) (1605.0 7025.0) (1605.0 6885.0) (2335.0 6885.0) (2335.0 7135.0) (1955.0 7135.0) (1955.0 7275.0) (-125.0 7275.0)) t) "CONC") hs nil)
 (setq o (upc:set (upc:pline ms '((3455.0 6885.0) (6228.0 6885.0) (6228.0 6792.1) (6265.0 6792.1) (6265.0 5235.0) (6465.0 5235.0) (6465.0 7375.0) (6452.0 7375.0) (6452.0 8875.0) (6575.0 8875.0) (6575.0 9125.0) (6452.0 9125.0) (6452.0 10135.0) (10685.0 10135.0) (10685.0 8330.0) (9775.0 8330.0) (9775.0 8130.0) (10685.0 8130.0) (10685.0 5490.0) (10885.0 5490.0) (10885.0 8130.0) (12815.0 8130.0) (12815.0 8330.0) (10885.0 8330.0) (10885.0 10135.0) (12455.0 10135.0) (12455.0 9545.0) (14685.0 9545.0) (14685.0 1690.0) (12720.0 1690.0) (12720.0 1495.0) (12705.0 1495.0) (12705.0 1490.0) (14685.0 1490.0) (14685.0 200.0) (14170.0 200.0) (14170.0 0.0) (14935.0 0.0) (14935.0 9745.0) (12655.0 9745.0) (12655.0 10135.0) (12705.0 10135.0) (12705.0 10335.0) (5445.0 10335.0) (5445.0 8875.0) (6228.0 8875.0) (6228.0 7135.0) (3455.0 7135.0)) t) "CONC") hs nil)
 (setq hs (cons (list (upc:set (upc:pline ms '((5695.0 9125.0) (5695.0 10135.0) (6228.0 10135.0) (6228.0 9125.0)) t) "CONC")) hs))
 (setq o (upc:set (upc:pline ms '((5965.0 1325.0) (6165.0 1325.0) (6165.0 4015.0) (5965.0 4015.0)) t) "CONC") hs nil)
 (setq o (upc:set (upc:pline ms '((10685.0 1325.0) (10885.0 1325.0) (10885.0 4510.0) (10685.0 4510.0)) t) "CONC") hs nil)
 (setq o (upc:set (upc:pline ms '((125.0 1325.0) (735.0 1325.0) (735.0 1515.0) (125.0 1515.0)) t) "WAL") hs nil)
 (upc:set (upc:hatch ms "ANSI31" 10 0 (list o) hs) "A_HAT")
 (setq o (upc:set (upc:pline ms '((2535.0 1325.0) (3705.0 1325.0) (3705.0 1515.0) (2535.0 1515.0)) t) "WAL") hs nil)
 (upc:set (upc:hatch ms "ANSI31" 10 0 (list o) hs) "A_HAT")
 (setq o (upc:set (upc:pline ms '((5505.0 1325.0) (5965.0 1325.0) (5965.0 1515.0) (5505.0 1515.0)) t) "WAL") hs nil)
 (upc:set (upc:hatch ms "ANSI31" 10 0 (list o) hs) "A_HAT")
 (setq o (upc:set (upc:pline ms '((5975.0 8570.0) (6228.0 8570.0) (6228.0 8760.0) (5975.0 8760.0)) t) "WAL") hs nil)
 (upc:set (upc:hatch ms "ANSI31" 10 0 (list o) hs) "A_HAT")
 (setq o (upc:set (upc:pline ms '((6165.0 1325.0) (6625.0 1325.0) (6625.0 1515.0) (6165.0 1515.0)) t) "WAL") hs nil)
 (upc:set (upc:hatch ms "ANSI31" 10 0 (list o) hs) "A_HAT")
 (setq o (upc:set (upc:pline ms '((6452.0 8570.0) (7175.0 8570.0) (7175.0 8760.0) (6452.0 8760.0)) t) "WAL") hs nil)
 (upc:set (upc:hatch ms "ANSI31" 10 0 (list o) hs) "A_HAT")
 (setq o (upc:set (upc:pline ms '((8675.0 8570.0) (10065.0 8570.0) (10065.0 8330.0) (10255.0 8330.0) (10255.0 8570.0) (10375.0 8570.0) (10375.0 8760.0) (10255.0 8760.0) (10255.0 10135.0) (10065.0 10135.0) (10065.0 8760.0) (8675.0 8760.0)) t) "WAL") hs nil)
 (upc:set (upc:hatch ms "ANSI31" 10 0 (list o) hs) "A_HAT")
 (setq o (upc:set (upc:pline ms '((10065.0 7950.0) (10255.0 7950.0) (10255.0 8130.0) (10065.0 8130.0)) t) "WAL") hs nil)
 (upc:set (upc:hatch ms "ANSI31" 10 0 (list o) hs) "A_HAT")
 (setq o (upc:set (upc:pline ms '((10225.0 1325.0) (10685.0 1325.0) (10685.0 1690.0) (10575.0 1690.0) (10575.0 1515.0) (10225.0 1515.0)) t) "WAL") hs nil)
 (upc:set (upc:hatch ms "ANSI31" 10 0 (list o) hs) "A_HAT")
 (setq o (upc:set (upc:pline ms '((10885.0 1325.0) (10995.0 1325.0) (10995.0 1500.0) (11220.0 1500.0) (11220.0 1690.0) (10885.0 1690.0)) t) "WAL") hs nil)
 (upc:set (upc:hatch ms "ANSI31" 10 0 (list o) hs) "A_HAT")
 (setq o (upc:set (upc:pline ms '((12815.0 8130.0) (13105.0 8130.0) (13105.0 8330.0) (12815.0 8330.0)) t) "WAL") hs nil)
 (upc:set (upc:hatch ms "ANSI31" 10 0 (list o) hs) "A_HAT")
 (setq o (upc:set (upc:pline ms '((14105.0 8130.0) (14685.0 8130.0) (14685.0 8330.0) (14105.0 8330.0)) t) "WAL") hs nil)
 (upc:set (upc:hatch ms "ANSI31" 10 0 (list o) hs) "A_HAT")
 (setq o (upc:set (upc:pline ms '((125.0 6375.0) (1745.0 6375.0) (1745.0 4955.0) (1845.0 4955.0) (1845.0 6885.0) (1745.0 6885.0) (1745.0 6475.0) (125.0 6475.0)) t) "WAL_DRY") hs nil)
 (setq o (upc:set (upc:pline ms '((1745.0 4115.0) (1845.0 4115.0) (1845.0 4135.0) (1745.0 4135.0)) t) "WAL_DRY") hs nil)
 (setq o (upc:set (upc:pline ms '((1955.0 3915.0) (2165.0 3915.0) (2165.0 4015.0) (1955.0 4015.0)) t) "WAL_DRY") hs nil)
 (setq o (upc:set (upc:pline ms '((3145.0 1515.0) (3245.0 1515.0) (3245.0 3915.0) (4985.0 3915.0) (4985.0 4015.0) (3145.0 4015.0)) t) "WAL_DRY") hs nil)
 (setq o (upc:set (upc:pline ms '((4265.0 5235.0) (4905.0 5235.0) (4905.0 5335.0) (4365.0 5335.0) (4365.0 6885.0) (4265.0 6885.0)) t) "WAL_DRY") hs nil)
 (setq o (upc:set (upc:pline ms '((5725.0 5235.0) (6265.0 5235.0) (6265.0 5335.0) (5725.0 5335.0)) t) "WAL_DRY") hs nil)
 (setq o (upc:set (upc:pline ms '((10885.0 5490.0) (12705.0 5490.0) (12705.0 5600.0) (12605.0 5600.0) (12605.0 5590.0) (10885.0 5590.0)) t) "WAL_DRY") hs nil)
 (setq o (upc:set (upc:pline ms '((10885.0 7040.0) (11440.0 7040.0) (11440.0 8130.0) (11340.0 8130.0) (11340.0 7140.0) (10885.0 7140.0)) t) "WAL_DRY") hs nil)
 (setq o (upc:set (upc:pline ms '((11340.0 8330.0) (11440.0 8330.0) (11440.0 10135.0) (11340.0 10135.0)) t) "WAL_DRY") hs nil)
 (setq o (upc:set (upc:pline ms '((12605.0 6420.0) (12705.0 6420.0) (12705.0 8130.0) (12605.0 8130.0)) t) "WAL_DRY") hs nil)
 (setq o (upc:set (upc:pline ms '((12605.0 8330.0) (12705.0 8330.0) (12705.0 9545.0) (12605.0 9545.0)) t) "WAL_DRY") hs nil)
 (setq o (upc:set (upc:pline ms '((12655.0 9745.0) (12705.0 9745.0) (12705.0 10135.0) (12655.0 10135.0)) t) "WAL_DRY") hs nil)
 (setq o (upc:set (upc:pline ms '((13905.0 5490.0) (14685.0 5490.0) (14685.0 5590.0) (13905.0 5590.0)) t) "WAL_DRY") hs nil)
 (upc:set (vla-addline ms (upc:pt 12640 5490) (upc:pt 12640 10335)) "CEN_WALL")
 (upc:set (vla-addline ms (upc:pt 12465.0 8145) (upc:pt 14935 8145)) "CEN_WALL")
 (upc:set (vla-addline ms (upc:pt 9775.0 8140) (upc:pt 12815.0 8140)) "CEN_CON")
 (upc:set (vla-addline ms (upc:pt 12455 9745) (upc:pt 14935.0 9745)) "CEN_CON")
 (upc:set (vla-addline ms (upc:pt 13905.0 5540) (upc:pt 14935 5540)) "CEN_WALL")
 (upc:set (vla-addline ms (upc:pt 5570 8875) (upc:pt 5570 10335)) "CEN_CON")
 (upc:set (vla-addline ms (upc:pt 1780 3915) (upc:pt 1780 7135)) "CEN_WALL")
 (upc:set (vla-addline ms (upc:pt 5445 9000) (upc:pt 6575.0 9000)) "CEN_CON")
 (upc:set (vla-addline ms (upc:pt 6340 6792.1) (upc:pt 6340 10335)) "CEN_CON")
 (upc:set (vla-addline ms (upc:pt 12555 9545) (upc:pt 12555 10335)) "CEN_CON")
 (upc:set (vla-addline ms (upc:pt 6365 5235) (upc:pt 6365 7375.0)) "CEN_CON")
 (upc:set (vla-addline ms (upc:pt 12705.0 1680) (upc:pt 14935 1680)) "CEN_CON")
 (upc:set (vla-addline ms (upc:pt 5975.0 8585) (upc:pt 10375.0 8585)) "CEN_WALL")
 (upc:set (vla-addline ms (upc:pt 10080 7950.0) (upc:pt 10080 10335)) "CEN_WALL")
 (upc:set (vla-addline ms (upc:pt 11390 7040) (upc:pt 11390 10335)) "CEN_WALL")
 (upc:set (vla-addline ms (upc:pt 10685 7090) (upc:pt 11440 7090)) "CEN_WALL")
 (upc:set (vla-addline ms (upc:pt 12780 0) (upc:pt 12780 1690)) "CEN_CON")
 (upc:set (vla-addline ms (upc:pt -125 1500) (upc:pt 10995.0 1500)) "CEN_WALL")
 (upc:set (vla-addline ms (upc:pt -125 4035) (upc:pt 1955.0 4035)) "CEN_CON")
 (upc:set (vla-addline ms (upc:pt 10785 1325) (upc:pt 10785 10335)) "CEN_CON")
 (upc:set (vla-addline ms (upc:pt 14630 0) (upc:pt 14630 9745)) "CEN_CON")
 (upc:set (vla-addline ms (upc:pt 10575.0 1675) (upc:pt 12880.0 1675)) "CEN_WALL")
 (upc:set (vla-addline ms (upc:pt 0.0 0) (upc:pt 14935.0 0)) "CEN_CON")
 (upc:set (vla-addline ms (upc:pt 10685 5555) (upc:pt 12705 5555)) "CEN_WALL")
 (upc:set (vla-addline ms (upc:pt 4265 5285) (upc:pt 6465 5285)) "CEN_WALL")
 (upc:set (vla-addline ms (upc:pt 6065 1325) (upc:pt 6065 4015)) "CEN_CON")
 (upc:set (vla-addline ms (upc:pt 1605.0 3965) (upc:pt 6165 3965)) "CEN_WALL")
 (upc:set (vla-addline ms (upc:pt 3195 1325) (upc:pt 3195 4015)) "CEN_WALL")
 (upc:set (vla-addline ms (upc:pt 0 0) (upc:pt 0 7275)) "CEN_CON")
 (upc:set (vla-addline ms (upc:pt 1605.0 7010) (upc:pt 6465 7010)) "CEN_CON")
 (upc:set (vla-addline ms (upc:pt 4315 5235) (upc:pt 4315 7135)) "CEN_WALL")
 (upc:set (vla-addline ms (upc:pt -125 7150) (upc:pt 1955.0 7150)) "CEN_CON")
 (upc:set (vla-addline ms (upc:pt -125 6425) (upc:pt 1845 6425)) "CEN_WALL")
 (upc:set (vla-addline ms (upc:pt 5445 10335) (upc:pt 12705 10335)) "CEN_CON"))))
