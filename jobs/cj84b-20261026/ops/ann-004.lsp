(upc:run "C:/temp/cj84b/outputs/cj84B-basic-v004.dwg" "C:/temp/cj84b/operations" "ann-004" (quote (lambda (doc / ms o hs h old) (setq ms (vla-get-modelspace doc)) (setq o (vla-addtext ms "침실2" (upc:pt 4250.0 2871.0) 120)) (vla-put-stylename o "HAUD01") (upc:set o "실명")
 (setq o (vla-addtext ms "침실3" (upc:pt 1408.0 2871.0) 120)) (vla-put-stylename o "HAUD01") (upc:set o "실명")
 (setq o (vla-addtext ms "거실" (upc:pt 8112.0 2869.0) 120)) (vla-put-stylename o "HAUD01") (upc:set o "실명")
 (setq o (vla-addtext ms "주방/식당" (upc:pt 8784.0 9684.0) 120)) (vla-put-stylename o "HAUD01") (upc:set o "실명")
 (setq o (vla-addtext ms "욕실2" (upc:pt 11752.0 6543.0) 120)) (vla-put-stylename o "HAUD01") (upc:set o "실명")
 (setq o (vla-addtext ms "침실1" (upc:pt 12156.0 3639.0) 120)) (vla-put-stylename o "HAUD01") (upc:set o "실명")
 (setq o (vla-addtext ms "현관" (upc:pt 3061.0 6176.0) 120)) (vla-put-stylename o "HAUD01") (upc:set o "실명")
 (setq o (vla-addtext ms "욕실1" (upc:pt 803.0 5134.0) 120)) (vla-put-stylename o "HAUD01") (upc:set o "실명")
 (setq o (vla-addtext ms "발코니1" (upc:pt 6319.0 900.0) 120)) (vla-put-stylename o "HAUD01") (upc:set o "실명")
 (setq o (vla-addtext ms "하향식피난구" (upc:pt 13280.0 896.0) 120)) (vla-put-stylename o "HAUD01") (upc:set o "실명")
 (setq o (vla-addtext ms "발코니2" (upc:pt 13812.0 4714.0) 120)) (vla-put-stylename o "HAUD01") (upc:set o "실명")
 (setq o (vla-addtext ms "발코니3" (upc:pt 11394.0 10200.0) 120)) (vla-put-stylename o "HAUD01") (upc:set o "실명")
 (setq o (vla-addtext ms "ELEV. 홀" (upc:pt 859.0 8055.0) 120)) (vla-put-stylename o "HAUD01") (upc:set o "실명")
 (setq o (vla-addtext ms "팬트리" (upc:pt 5436.0 6083.0) 120)) (vla-put-stylename o "HAUD01") (upc:set o "실명"))))
