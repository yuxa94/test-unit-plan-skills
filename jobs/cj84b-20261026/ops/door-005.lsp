(upc:run "C:/temp/cj84b/outputs/cj84B-basic-v005.dwg" "C:/temp/cj84b/operations" "door-005" (quote (lambda (doc / ms o hs h old) (setq ms (vla-get-modelspace doc)) (upc:set (vla-addline ms (upc:pt 1745.0 4103.5) (upc:pt 1845.0 4103.5)) "DOOR")
 (upc:set (vla-addline ms (upc:pt 1745.0 4903.5) (upc:pt 1845.0 4903.5)) "DOOR")
 (upc:set (vla-addline ms (upc:pt 1745.0 4103.5) (upc:pt 945.0 4103.5)) "DOOR")
 (upc:set (vla-addarc ms (upc:pt 1745.0 4103.5) 800 1.570796 3.141593) "DOOR")
 (upc:set (vla-addline ms (upc:pt 11851.5 5490.0) (upc:pt 11851.5 5590.0)) "DOOR")
 (upc:set (vla-addline ms (upc:pt 12651.5 5490.0) (upc:pt 12651.5 5590.0)) "DOOR")
 (upc:set (vla-addline ms (upc:pt 12651.5 5590.0) (upc:pt 12651.5 6390.0)) "DOOR")
 (upc:set (vla-addarc ms (upc:pt 12651.5 5590.0) 800 1.570796 3.141593) "DOOR")
 (upc:set (vla-addline ms (upc:pt 2880.0 7025.0) (upc:pt 2880.0 7275.0)) "DOOR")
 (upc:set (vla-addline ms (upc:pt 3980.0 7025.0) (upc:pt 3980.0 7275.0)) "DOOR")
 (upc:set (vla-addline ms (upc:pt 3980.0 7275.0) (upc:pt 3980.0 8375.0)) "DOOR")
 (upc:set (vla-addarc ms (upc:pt 3980.0 7275.0) 1100 1.570796 3.141593) "DOOR")
 (upc:set (vla-addline ms (upc:pt 10685.0 4490.0) (upc:pt 10885.0 4490.0)) "DOOR")
 (upc:set (vla-addline ms (upc:pt 10685.0 5390.0) (upc:pt 10885.0 5390.0)) "DOOR")
 (upc:set (vla-addline ms (upc:pt 10885.0 5390.0) (upc:pt 11785.0 5390.0)) "DOOR")
 (upc:set (vla-addarc ms (upc:pt 10885.0 5390.0) 900 -1.570796 0.000000) "DOOR")
 (upc:set (vla-addline ms (upc:pt 4965.0 3915.0) (upc:pt 4965.0 4015.0)) "DOOR")
 (upc:set (vla-addline ms (upc:pt 5865.0 3915.0) (upc:pt 5865.0 4015.0)) "DOOR")
 (upc:set (vla-addline ms (upc:pt 5865.0 3915.0) (upc:pt 5865.0 3015.0)) "DOOR")
 (upc:set (vla-addarc ms (upc:pt 5865.0 3915.0) 900 3.141593 -1.570796) "DOOR")
 (upc:set (vla-addline ms (upc:pt 2145.0 3915.0) (upc:pt 2145.0 4015.0)) "DOOR")
 (upc:set (vla-addline ms (upc:pt 3045.0 3915.0) (upc:pt 3045.0 4015.0)) "DOOR")
 (upc:set (vla-addline ms (upc:pt 3045.0 3915.0) (upc:pt 3045.0 3015.0)) "DOOR")
 (upc:set (vla-addarc ms (upc:pt 3045.0 3915.0) 900 3.141593 -1.570796) "DOOR")
 (upc:set (vla-addline ms (upc:pt 5295.0 5235.0) (upc:pt 5295.0 5335.0)) "DOOR")
 (upc:set (vla-addline ms (upc:pt 6095.0 5235.0) (upc:pt 6095.0 5335.0)) "DOOR")
 (upc:set (vla-addline ms (upc:pt 5295.0 5335.0) (upc:pt 5295.0 6135.0)) "DOOR")
 (upc:set (vla-addarc ms (upc:pt 5295.0 5335.0) 800 0.000000 1.570796) "DOOR")
 (upc:set (vla-addline ms (upc:pt 12925.0 750.0) (upc:pt 13045.0 750.0)) "DOOR")
 (upc:set (vla-addline ms (upc:pt 12925.0 1500.0) (upc:pt 13045.0 1500.0)) "DOOR")
 (upc:set (upc:pline ms '((12940.0 750.0) (12940.0 1175.0) (12980.0 1175.0) (12980.0 750.0)) t) "DOOR")
 (upc:set (upc:pline ms '((12990.0 1075.0) (12990.0 1500.0) (13030.0 1500.0) (13030.0 1075.0)) t) "DOOR"))))
