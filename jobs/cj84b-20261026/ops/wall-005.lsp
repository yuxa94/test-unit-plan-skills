(upc:run "C:/temp/cj84b/outputs/cj84B-basic-v005.dwg" "C:/temp/cj84b/operations" "wall-005" (quote (lambda (doc / ms o hs h old) (setq ms (vla-get-modelspace doc)) (setq o (upc:set (upc:pline ms '((-125.0 0.0) (13437.5 0.0) (13437.5 200.0) (13045.0 200.0) (13045.0 750.0) (12925.0 750.0) (12925.0 200.0) (125.0 200.0) (125.0 3915.0) (1955.0 3915.0) (1955.0 4115.0) (1850.0 4115.0) (1850.0 4103.5) (1740.0 4103.5) (1740.0 4115.0) (125.0 4115.0) (125.0 7025.0) (2880.0 7025.0) (2880.0 7275.0) (-125.0 7275.0)) t) "CONC") hs nil)
 (setq o (upc:set (upc:pline ms '((3980.0 7025.0) (6425.0 7025.0) (6425.0 6775.0) (6615.0 6775.0) (6615.0 5235.0) (6815.0 5235.0) (6815.0 7375.0) (6675.0 7375.0) (6675.0 11000.0) (12180.0 11000.0) (12180.0 8760.0) (10885.0 8760.0) (10885.0 8828.4) (10685.0 8828.4) (10685.0 8760.0) (10575.0 8760.0) (10575.0 8560.0) (10685.0 8560.0) (10685.0 5390.0) (10885.0 5390.0) (10885.0 8560.0) (14700.0 8560.0) (14700.0 1690.0) (13045.0 1690.0) (13045.0 1980.0) (12925.0 1980.0) (12925.0 1690.0) (12910.0 1690.0) (12910.0 1490.0) (12920.0 1490.0) (12920.0 1500.0) (13050.0 1500.0) (13050.0 1490.0) (14700.0 1490.0) (14700.0 200.0) (14437.5 200.0) (14437.5 0.0) (14900.0 0.0) (14900.0 8760.0) (12380.0 8760.0) (12380.0 11250.0) (12180.0 11250.0) (12180.0 11100.0) (6675.0 11100.0) (6675.0 11725.0) (6425.0 11725.0) (6425.0 7275.0) (3980.0 7275.0)) t) "CONC") hs nil)
 (setq o (upc:set (upc:pline ms '((5965.0 1325.0) (6165.0 1325.0) (6165.0 4015.0) (5965.0 4015.0)) t) "CONC") hs nil)
 (setq o (upc:set (upc:pline ms '((10685.0 1325.0) (10885.0 1325.0) (10885.0 4490.0) (10685.0 4490.0)) t) "CONC") hs nil)
 (setq o (upc:set (upc:pline ms '((125.0 1325.0) (675.0 1325.0) (675.0 1515.0) (125.0 1515.0)) t) "WAL") hs nil)
 (upc:set (upc:hatch ms "ANSI31" 10 0 (list o) hs) "A_HAT")
 (setq o (upc:set (upc:pline ms '((2475.0 1325.0) (3725.0 1325.0) (3725.0 1515.0) (2475.0 1515.0)) t) "WAL") hs nil)
 (upc:set (upc:hatch ms "ANSI31" 10 0 (list o) hs) "A_HAT")
 (setq o (upc:set (upc:pline ms '((5525.0 1325.0) (5965.0 1325.0) (5965.0 1515.0) (5525.0 1515.0)) t) "WAL") hs nil)
 (upc:set (upc:hatch ms "ANSI31" 10 0 (list o) hs) "A_HAT")
 (setq o (upc:set (upc:pline ms '((6165.0 1325.0) (6625.0 1325.0) (6625.0 1515.0) (6165.0 1515.0)) t) "WAL") hs nil)
 (upc:set (upc:hatch ms "ANSI31" 10 0 (list o) hs) "A_HAT")
 (setq o (upc:set (upc:pline ms '((10065.0 7660.0) (10685.0 7660.0) (10685.0 7750.0) (10155.0 7750.0) (10155.0 8650.0) (10575.0 8650.0) (10575.0 8760.0) (10065.0 8760.0)) t) "WAL") hs nil)
 (upc:set (upc:hatch ms "ANSI31" 10 0 (list o) hs) "A_HAT")
 (setq o (upc:set (upc:pline ms '((10225.0 1325.0) (10685.0 1325.0) (10685.0 1690.0) (10575.0 1690.0) (10575.0 1515.0) (10225.0 1515.0)) t) "WAL") hs nil)
 (upc:set (upc:hatch ms "ANSI31" 10 0 (list o) hs) "A_HAT")
 (setq o (upc:set (upc:pline ms '((10865.0 8828.4) (10885.0 8828.4) (10885.0 8760.0) (11055.0 8760.0) (11055.0 9165.0) (10865.0 9165.0)) t) "WAL") hs nil)
 (upc:set (upc:hatch ms "ANSI31" 10 0 (list o) hs) "A_HAT")
 (setq o (upc:set (upc:pline ms '((10865.0 10465.0) (11055.0 10465.0) (11055.0 11000.0) (10865.0 11000.0)) t) "WAL") hs nil)
 (upc:set (upc:hatch ms "ANSI31" 10 0 (list o) hs) "A_HAT")
 (setq o (upc:set (upc:pline ms '((10865.0 11100.0) (11055.0 11100.0) (11055.0 11725.0) (10865.0 11725.0)) t) "WAL") hs nil)
 (upc:set (upc:hatch ms "ANSI31" 10 0 (list o) hs) "A_HAT")
 (setq o (upc:set (upc:pline ms '((10885.0 1325.0) (10995.0 1325.0) (10995.0 1500.0) (11125.0 1500.0) (11125.0 1690.0) (10885.0 1690.0)) t) "WAL") hs nil)
 (upc:set (upc:hatch ms "ANSI31" 10 0 (list o) hs) "A_HAT")
 (setq o (upc:set (upc:pline ms '((10885.0 8240.0) (11055.0 8240.0) (11055.0 8560.0) (10885.0 8560.0)) t) "WAL") hs nil)
 (upc:set (upc:hatch ms "ANSI31" 10 0 (list o) hs) "A_HAT")
 (setq o (upc:set (upc:pline ms '((12625.0 1500.0) (12910.0 1500.0) (12910.0 1690.0) (12625.0 1690.0)) t) "WAL") hs nil)
 (upc:set (upc:hatch ms "ANSI31" 10 0 (list o) hs) "A_HAT")
 (setq o (upc:set (upc:pline ms '((12765.0 5490.0) (12955.0 5490.0) (12955.0 8560.0) (12765.0 8560.0)) t) "WAL") hs nil)
 (upc:set (upc:hatch ms "ANSI31" 10 0 (list o) hs) "A_HAT")
 (setq o (upc:set (upc:pline ms '((13385.0 200.0) (13437.5 200.0) (13437.5 205.0) (13575.0 205.0) (13575.0 1490.0) (13385.0 1490.0)) t) "WAL") hs nil)
 (upc:set (upc:hatch ms "ANSI31" 10 0 (list o) hs) "A_HAT")
 (setq o (upc:set (upc:pline ms '((13385.0 1690.0) (13575.0 1690.0) (13575.0 2575.0) (13385.0 2575.0)) t) "WAL") hs nil)
 (upc:set (upc:hatch ms "ANSI31" 10 0 (list o) hs) "A_HAT")
 (setq o (upc:set (upc:pline ms '((13385.0 4675.0) (13575.0 4675.0) (13575.0 5860.0) (13385.0 5860.0)) t) "WAL") hs nil)
 (upc:set (upc:hatch ms "ANSI31" 10 0 (list o) hs) "A_HAT")
 (setq o (upc:set (upc:pline ms '((125.0 6405.0) (1745.0 6405.0) (1745.0 4903.5) (1845.0 4903.5) (1845.0 5235.0) (5295.0 5235.0) (5295.0 5335.0) (4745.0 5335.0) (4745.0 7025.0) (4645.0 7025.0) (4645.0 5335.0) (2225.0 5335.0) (2225.0 7025.0) (2150.0 7025.0) (2150.0 5335.0) (1845.0 5335.0) (1845.0 6480.0) (125.0 6480.0)) t) "WAL_DRY") hs nil)
 (setq o (upc:set (upc:pline ms '((1955.0 3915.0) (2145.0 3915.0) (2145.0 4015.0) (1955.0 4015.0)) t) "WAL_DRY") hs nil)
 (setq o (upc:set (upc:pline ms '((3045.0 3915.0) (3145.0 3915.0) (3145.0 1515.0) (3245.0 1515.0) (3245.0 3915.0) (4965.0 3915.0) (4965.0 4015.0) (3045.0 4015.0)) t) "WAL_DRY") hs nil)
 (setq o (upc:set (upc:pline ms '((5865.0 3915.0) (5965.0 3915.0) (5965.0 4015.0) (5865.0 4015.0)) t) "WAL_DRY") hs nil)
 (setq o (upc:set (upc:pline ms '((6095.0 5235.0) (6615.0 5235.0) (6615.0 5335.0) (6095.0 5335.0)) t) "WAL_DRY") hs nil)
 (setq o (upc:set (upc:pline ms '((10885.0 5490.0) (11851.5 5490.0) (11851.5 5590.0) (10885.0 5590.0)) t) "WAL_DRY") hs nil)
 (setq o (upc:set (upc:pline ms '((10885.0 7070.0) (11395.0 7070.0) (11395.0 7970.0) (12765.0 7970.0) (12765.0 8045.0) (11320.0 8045.0) (11320.0 7145.0) (10885.0 7145.0)) t) "WAL_DRY") hs nil)
 (setq o (upc:set (upc:pline ms '((12651.5 5490.0) (12765.0 5490.0) (12765.0 5590.0) (12651.5 5590.0)) t) "WAL_DRY") hs nil)
 (setq o (upc:set (upc:pline ms '((12955.0 5490.0) (13385.0 5490.0) (13385.0 5590.0) (12955.0 5590.0)) t) "WAL_DRY") hs nil)
 (upc:set (vla-addline ms (upc:pt 2175.0 5235.0) (upc:pt 2175.0 7275.0)) "CEN_WALL")
 (upc:set (vla-addline ms (upc:pt 0.0 0.0) (upc:pt 0.0 7275.0)) "CEN_CON")
 (upc:set (vla-addline ms (upc:pt 1780.0 3915.0) (upc:pt 1780.0 6480.0)) "CEN_WALL")
 (upc:set (vla-addline ms (upc:pt 10065.0 8695.0) (upc:pt 11055.0 8695.0)) "CEN_WALL")
 (upc:set (vla-addline ms (upc:pt 10110.0 7660.0) (upc:pt 10110.0 8760.0)) "CEN_WALL")
 (upc:set (vla-addline ms (upc:pt 10065.0 7705.0) (upc:pt 10885.0 7705.0)) "CEN_WALL")
 (upc:set (vla-addline ms (upc:pt 1605.0 7010.0) (upc:pt 6815.0 7010.0)) "CEN_CON")
 (upc:set (vla-addline ms (upc:pt 4695.0 5235.0) (upc:pt 4695.0 7275.0)) "CEN_WALL")
 (upc:set (vla-addline ms (upc:pt -125.0 7150.0) (upc:pt 2225.0 7150.0)) "CEN_CON")
 (upc:set (vla-addline ms (upc:pt -125.0 6425.0) (upc:pt 1845.0 6425.0)) "CEN_WALL")
 (upc:set (vla-addline ms (upc:pt 11320.0 7990.0) (upc:pt 12955.0 7990.0)) "CEN_WALL")
 (upc:set (vla-addline ms (upc:pt 10575.0 8660.0) (upc:pt 14900.0 8660.0)) "CEN_CON")
 (upc:set (vla-addline ms (upc:pt 6425.0 10945.0) (upc:pt 12380.0 10945.0)) "CEN_CON")
 (upc:set (vla-addline ms (upc:pt 12910.0 1680.0) (upc:pt 14900.0 1680.0)) "CEN_CON")
 (upc:set (vla-addline ms (upc:pt 12380.0 8560.0) (upc:pt 12380.0 11250.0)) "CEN_CON")
 (upc:set (vla-addline ms (upc:pt 6690.0 6775.0) (upc:pt 6690.0 11725.0)) "CEN_CON")
 (upc:set (vla-addline ms (upc:pt 6715.0 5235.0) (upc:pt 6715.0 7375.0)) "CEN_CON")
 (upc:set (vla-addline ms (upc:pt 12985.0 0.0) (upc:pt 12985.0 1980.0)) "CEN_CON")
 (upc:set (vla-addline ms (upc:pt 10575.0 1675.0) (upc:pt 13085.0 1675.0)) "CEN_WALL")
 (upc:set (vla-addline ms (upc:pt 1745.0 5285.0) (upc:pt 6815.0 5285.0)) "CEN_WALL")
 (upc:set (vla-addline ms (upc:pt 6065.0 1325.0) (upc:pt 6065.0 4015.0)) "CEN_CON")
 (upc:set (vla-addline ms (upc:pt 1605.0 3965.0) (upc:pt 6165.0 3965.0)) "CEN_WALL")
 (upc:set (vla-addline ms (upc:pt 3195.0 1325.0) (upc:pt 3195.0 4015.0)) "CEN_WALL")
 (upc:set (vla-addline ms (upc:pt 0.0 0.0) (upc:pt 0.0 7275.0)) "CEN_CON")
 (upc:set (vla-addline ms (upc:pt -125.0 1500.0) (upc:pt 10995.0 1500.0)) "CEN_WALL")
 (upc:set (vla-addline ms (upc:pt -125.0 4035.0) (upc:pt 1955.0 4035.0)) "CEN_CON")
 (upc:set (vla-addline ms (upc:pt 10785.0 1325.0) (upc:pt 10785.0 8828.4)) "CEN_CON")
 (upc:set (vla-addline ms (upc:pt -125.0 0.0) (upc:pt 14900.0 0.0)) "CEN_CON")
 (upc:set (vla-addline ms (upc:pt 13400.0 0.0) (upc:pt 13400.0 5860.0)) "CEN_WALL")
 (upc:set (vla-addline ms (upc:pt 14900.0 0.0) (upc:pt 14900.0 8760.0)) "CEN_CON")
 (upc:set (vla-addline ms (upc:pt 10685.0 5555.0) (upc:pt 13575.0 5555.0)) "CEN_WALL")
 (upc:set (vla-addline ms (upc:pt 12775.0 5490.0) (upc:pt 12775.0 8760.0)) "CEN_WALL")
 (upc:set (vla-addline ms (upc:pt 11390.0 7070.0) (upc:pt 11390.0 8045.0)) "CEN_WALL")
 (upc:set (vla-addline ms (upc:pt 10685.0 7090.0) (upc:pt 11395.0 7090.0)) "CEN_WALL")
 (upc:set (vla-addline ms (upc:pt 10880.0 8240.0) (upc:pt 10880.0 11725.0)) "CEN_WALL"))))
