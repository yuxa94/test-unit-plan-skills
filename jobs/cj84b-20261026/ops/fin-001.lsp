(upc:run "C:/temp/cj84b/outputs/cj84B-basic-v001.dwg" "C:/temp/cj84b/operations" "fin-001" (quote (lambda (doc / ms o hs h old) (setq ms (vla-get-modelspace doc)) (upc:set (upc:pline ms '((3245.0 1625.0) (5965.0 1625.0) (5965.0 3915.0) (3245.0 3915.0)) t) "FIN")
 (upc:set (upc:pline ms '((125.0 1625.0) (3145.0 1625.0) (3145.0 3915.0) (125.0 3915.0)) t) "FIN")
 (upc:set (upc:pline ms '((1845.0 4115.0) (1955.0 4115.0) (1955.0 4015.0) (6165.0 4015.0) (6165.0 1625.0) (10575.0 1625.0) (10575.0 1800.0) (10685.0 1800.0) (10685.0 5285.0) (6815.0 5285.0) (6815.0 5235.0) (1845.0 5235.0)) t) "FIN")
 (upc:set (upc:pline ms '((6690.0 10900.0) (6785.0 10900.0) (6785.0 7375.0) (6925.0 7375.0) (6925.0 6947.0) (6815.0 6947.0) (6815.0 5285.0) (10685.0 5285.0) (10685.0 7161.0) (10575.0 7161.0) (10575.0 7550.0) (10065.0 7550.0) (10065.0 7660.0) (9955.0 7660.0) (9955.0 8760.0) (10065.0 8760.0) (10065.0 8870.0) (10755.0 8870.0) (10755.0 10853.8) (10865.0 10853.8) (10865.0 10945.0) (10678.6 10945.0) (10678.6 10890.0) (6850.4 10890.0) (6850.4 10945.0) (6690.0 10945.0)) t) "FIN")
 (upc:set (upc:pline ms '((10885.0 5590.0) (12655.0 5590.0) (12655.0 7942.5) (12765.0 7942.5) (12765.0 7970.0) (11395.0 7970.0) (11395.0 7070.0) (10885.0 7070.0)) t) "FIN")
 (upc:set (upc:pline ms '((10885.0 1800.0) (12925.0 1800.0) (12925.0 1980.0) (13045.0 1980.0) (13045.0 1800.0) (13275.0 1800.0) (13275.0 5441.4) (13385.0 5441.4) (13385.0 5490.0) (10885.0 5490.0)) t) "FIN")
 (upc:set (upc:pline ms '((2225.0 5335.0) (4645.0 5335.0) (4645.0 6915.0) (2225.0 6915.0)) t) "FIN")
 (upc:set (upc:pline ms '((125.0 4115.0) (1745.0 4115.0) (1745.0 6405.0) (125.0 6405.0)) t) "FIN")
 (upc:set (upc:pline ms '((125.0 200.0) (12925.0 200.0) (12925.0 1490.0) (12910.0 1490.0) (12910.0 1500.0) (10995.0 1500.0) (10995.0 1325.0) (125.0 1325.0)) t) "FIN")
 (upc:set (upc:pline ms '((13045.0 200.0) (13385.0 200.0) (13385.0 1490.0) (13045.0 1490.0)) t) "FIN")
 (upc:set (upc:pline ms '((13575.0 200.0) (14700.0 200.0) (14700.0 1490.0) (13575.0 1490.0)) t) "FIN")
 (upc:set (upc:pline ms '((12955.0 5590.0) (13385.0 5590.0) (13385.0 5860.0) (13575.0 5860.0) (13575.0 1690.0) (14700.0 1690.0) (14700.0 8560.0) (12955.0 8560.0)) t) "FIN")
 (upc:set (upc:pline ms '((11055.0 8760.0) (12180.0 8760.0) (12180.0 10945.0) (11055.0 10945.0)) t) "FIN")
 (upc:set (upc:pline ms '((4745.0 5335.0) (6615.0 5335.0) (6615.0 6775.0) (6425.0 6775.0) (6425.0 6915.0) (4745.0 6915.0)) t) "FIN")
 (setq o (upc:pline ms '((125.0 200.0) (12925.0 200.0) (12925.0 1490.0) (12910.0 1490.0) (12910.0 1500.0) (10995.0 1500.0) (10995.0 1325.0) (125.0 1325.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((13045.0 200.0) (13385.0 200.0) (13385.0 1490.0) (13045.0 1490.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((13575.0 200.0) (14700.0 200.0) (14700.0 1490.0) (13575.0 1490.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((12955.0 5590.0) (13385.0 5590.0) (13385.0 5860.0) (13575.0 5860.0) (13575.0 1690.0) (14700.0 1690.0) (14700.0 8560.0) (12955.0 8560.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일")
 (setq o (upc:pline ms '((11055.0 8760.0) (12180.0 8760.0) (12180.0 10945.0) (11055.0 10945.0)) t)) (upc:set o "바닥타일") (setq h (vla-addhatch ms acHatchPatternTypeUserDefined "_USER" :vlax-true)) (vla-put-patternspace h 300) (vla-put-patterndouble h :vlax-true) (vla-appendouterloop h (upc:objarray (list o))) (vla-evaluate h) (upc:set h "바닥타일"))))
