(upc:run "C:/temp/cj84b/outputs/cj84B-basic-v002.dwg" "C:/temp/cj84b/operations" "dim-002" (quote (lambda (doc / ms o hs h old) (setq ms (vla-get-modelspace doc)) (setq o (vla-adddimrotated ms (upc:pt 0 0) (upc:pt 14900 0) (upc:pt 7450.0 -1500) 0)) (vla-put-stylename o "MCDIM-50") (upc:set o "DIM")
 (setq o (vla-adddimrotated ms (upc:pt 0 0) (upc:pt 12985 0) (upc:pt 6492.5 -900) 0)) (vla-put-stylename o "MCDIM-50") (upc:set o "DIM")
 (setq o (vla-adddimrotated ms (upc:pt 12985 0) (upc:pt 13400 0) (upc:pt 13192.5 -900) 0)) (vla-put-stylename o "MCDIM-50") (upc:set o "DIM")
 (setq o (vla-adddimrotated ms (upc:pt 13400 0) (upc:pt 14900 0) (upc:pt 14150.0 -900) 0)) (vla-put-stylename o "MCDIM-50") (upc:set o "DIM")
 (setq o (vla-adddimrotated ms (upc:pt 14900 0) (upc:pt 14900 8660) (upc:pt 16600 4330.0) (/ pi 2))) (vla-put-stylename o "MCDIM-50") (upc:set o "DIM")
 (setq o (vla-adddimrotated ms (upc:pt 14900 0) (upc:pt 14900 1680) (upc:pt 16000 840.0) (/ pi 2))) (vla-put-stylename o "MCDIM-50") (upc:set o "DIM")
 (setq o (vla-adddimrotated ms (upc:pt 14900 1680) (upc:pt 14900 8660) (upc:pt 16000 5170.0) (/ pi 2))) (vla-put-stylename o "MCDIM-50") (upc:set o "DIM")
 (setq o (vla-adddimrotated ms (upc:pt 3245.0 2571.0) (upc:pt 5965.0 2571.0) (upc:pt 4605.0 2571.0) 0)) (vla-put-stylename o "HAUD-100") (upc:set o "DIM")
 (setq o (vla-adddimrotated ms (upc:pt 5000.0 1625.0) (upc:pt 5000.0 3915.0) (upc:pt 5000.0 2770.0) (/ pi 2))) (vla-put-stylename o "HAUD-100") (upc:set o "DIM")
 (setq o (vla-adddimrotated ms (upc:pt 125.0 2571.0) (upc:pt 3145.0 2571.0) (upc:pt 1635.0 2571.0) 0)) (vla-put-stylename o "HAUD-100") (upc:set o "DIM")
 (setq o (vla-adddimrotated ms (upc:pt 2158.0 1625.0) (upc:pt 2158.0 3915.0) (upc:pt 2158.0 2770.0) (/ pi 2))) (vla-put-stylename o "HAUD-100") (upc:set o "DIM")
 (setq o (vla-adddimrotated ms (upc:pt 6165.0 2569.0) (upc:pt 10685.0 2569.0) (upc:pt 8425.0 2569.0) 0)) (vla-put-stylename o "HAUD-100") (upc:set o "DIM")
 (setq o (vla-adddimrotated ms (upc:pt 8862.0 1625.0) (upc:pt 8862.0 5285) (upc:pt 8862.0 3455.0) (/ pi 2))) (vla-put-stylename o "HAUD-100") (upc:set o "DIM")
 (setq o (vla-adddimrotated ms (upc:pt 6785.0 9384.0) (upc:pt 10755.0 9384.0) (upc:pt 8770.0 9384.0) 0)) (vla-put-stylename o "HAUD-100") (upc:set o "DIM")
 (setq o (vla-adddimrotated ms (upc:pt 9534.0 5285) (upc:pt 9534.0 10890.0) (upc:pt 9534.0 8087.5) (/ pi 2))) (vla-put-stylename o "HAUD-100") (upc:set o "DIM")
 (setq o (vla-adddimrotated ms (upc:pt 10885.0 3339.0) (upc:pt 13275.0 3339.0) (upc:pt 12080.0 3339.0) 0)) (vla-put-stylename o "HAUD-100") (upc:set o "DIM")
 (setq o (vla-adddimrotated ms (upc:pt 12906.0 1800.0) (upc:pt 12906.0 5490.0) (upc:pt 12906.0 3645.0) (/ pi 2))) (vla-put-stylename o "HAUD-100") (upc:set o "DIM"))))
