(upc:run "C:/temp/cj84b/outputs/cj84B-basic-v001.dwg" "C:/temp/cj84b/operations" "win-001" (quote (lambda (doc / ms o hs h old) (setq ms (vla-get-modelspace doc)) (upc:set (upc:pline ms '((6625.0 1325.0) (10225.0 1325.0) (10225.0 1515.0) (6625.0 1515.0)) t) "WIN")
 (upc:set (vla-addline ms (upc:pt 6625.0 1391.5) (upc:pt 10225.0 1391.5)) "WIN")
 (upc:set (vla-addline ms (upc:pt 6625.0 1448.5) (upc:pt 10225.0 1448.5)) "WIN")
 (upc:set (upc:pline ms '((11125.0 1500.0) (12625.0 1500.0) (12625.0 1690.0) (11125.0 1690.0)) t) "WIN")
 (upc:set (vla-addline ms (upc:pt 11125.0 1566.5) (upc:pt 12625.0 1566.5)) "WIN")
 (upc:set (vla-addline ms (upc:pt 11125.0 1623.5) (upc:pt 12625.0 1623.5)) "WIN")
 (upc:set (upc:pline ms '((13385.0 2575.0) (13385.0 4675.0) (13575.0 4675.0) (13575.0 2575.0)) t) "WIN")
 (upc:set (vla-addline ms (upc:pt 13451.5 2575.0) (upc:pt 13451.5 4675.0)) "WIN")
 (upc:set (vla-addline ms (upc:pt 13508.5 2575.0) (upc:pt 13508.5 4675.0)) "WIN")
 (upc:set (upc:pline ms '((3725.0 1325.0) (5525.0 1325.0) (5525.0 1515.0) (3725.0 1515.0)) t) "WIN")
 (upc:set (vla-addline ms (upc:pt 3725.0 1391.5) (upc:pt 5525.0 1391.5)) "WIN")
 (upc:set (vla-addline ms (upc:pt 3725.0 1448.5) (upc:pt 5525.0 1448.5)) "WIN")
 (upc:set (upc:pline ms '((675.0 1325.0) (2475.0 1325.0) (2475.0 1515.0) (675.0 1515.0)) t) "WIN")
 (upc:set (vla-addline ms (upc:pt 675.0 1391.5) (upc:pt 2475.0 1391.5)) "WIN")
 (upc:set (vla-addline ms (upc:pt 675.0 1448.5) (upc:pt 2475.0 1448.5)) "WIN")
 (upc:set (upc:pline ms '((10865.0 9165.0) (10865.0 10465.0) (11055.0 10465.0) (11055.0 9165.0)) t) "WIN")
 (upc:set (vla-addline ms (upc:pt 10931.5 9165.0) (upc:pt 10931.5 10465.0)) "WIN")
 (upc:set (vla-addline ms (upc:pt 10988.5 9165.0) (upc:pt 10988.5 10465.0)) "WIN")
 (upc:set (upc:pline ms '((13437.5 0.0) (14437.5 0.0) (14437.5 200.0) (13437.5 200.0)) t) "WIN")
 (upc:set (vla-addline ms (upc:pt 13437.5 100.0) (upc:pt 14437.5 100.0)) "WIN"))))
